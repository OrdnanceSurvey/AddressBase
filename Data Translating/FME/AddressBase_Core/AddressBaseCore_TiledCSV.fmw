FME workspace AddressBaseCore_TiledCSV.fmw

Parameters:
- SourceDataset_CSV2_3 = ""..\SU0000.zip" "..\SU0005.zip" "..\SU0010.zip""   # Source CSV (Comma Separated Value) File(s)
- DestDataset_CSV2_3 = C:\DATA   # Destination CSV (Comma Separated Value) Folder

Readers:
- CSV2_1: CSV2 from $(SourceDataset_CSV2_3) in EPSG:27700

Writers:
- CSV2_2: CSV2 to $(DestDataset_CSV2_3)

AttributeManager
    ATTR_TABLE = RENAME_SET_VALUE fme_basename > tilename
    -> ABCore_Tiled_Combined (writer CSV2_2)

Bookmark: ABCore CSVs
Note: Select all downloaded CSV zip files from local drive.
CSV (reader CSV2_1)
    attributes: UPRN uint64, PARENT_UPRN uint64, UDPRN uint32, USRN uint32, TOID string, CLASSIFICATION_CODE string, EASTING real64, NORTHING real64, LATITUDE y_coordinate, LONGITUDE x_coordinate, RPC uint8, LAST_UPDATE_DATE string, SINGLE_LINE_ADDRESS string, PO_BOX string, ORGANISATION string, SUB_BUILDING string, BUILDING_NAME string, BUILDING_NUMBER string, STREET_NAME string, LOCALITY string, TOWN_NAME string, POST_TOWN string, ISLAND string, POSTCODE string, DELIVERY_POINT_SUFFIX string, GSS_CODE string, CHANGE_CODE string
    -> AttributeManager

Bookmark: ABCore Combined CSVs
ABCore_Tiled_Combined (writer CSV2_2)
    attributes: UPRN uint64, PARENT_UPRN uint64, UDPRN uint32, USRN uint32, TOID string, CLASSIFICATION_CODE string, EASTING real64, NORTHING real64, LATITUDE y_coordinate, LONGITUDE x_coordinate, RPC uint8, LAST_UPDATE_DATE string, SINGLE_LINE_ADDRESS string, PO_BOX string, ORGANISATION string, SUB_BUILDING string, BUILDING_NAME string, BUILDING_NUMBER string, STREET_NAME string, LOCALITY string, TOWN_NAME string, POST_TOWN string, ISLAND string, POSTCODE string, DELIVERY_POINT_SUFFIX string, GSS_CODE string, CHANGE_CODE string, tilename string
